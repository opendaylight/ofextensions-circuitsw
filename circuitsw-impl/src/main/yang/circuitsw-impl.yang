module circuitsw-impl {
    yang-version 1;
    namespace "urn:opendaylight:params:xml:ns:yang:circuitsw:impl";
    prefix "circuitsw-impl";

    import config { prefix config; revision-date 2013-04-05; }
    import opendaylight-md-sal-binding { prefix md-sal-binding; revision-date 2013-10-28;}

    description
        "Service definition for circuitsw project";

    revision "2015-10-13" {
        description
            "Initial revision";
    }

    identity circuitsw {
        base config:module-type;
        config:java-name-prefix Circuitsw;
    }

    augment "/config:modules/config:module/config:configuration" {
        case circuitsw {
            when "/config:modules/config:module/config:type = 'circuitsw'";
            container broker {
                uses config:service-ref {
                    refine type {
                        mandatory true;
                        config:required-identity md-sal-binding:binding-broker-osgi-registry;
                    }
                }
            }
        }
    }
}
